FME workspace ml_after.fmw

Parameters:
- SourceDataset_IFC = ""C:\Users\simay\OneDrive\Desktop\sb_fme\new_data\Tallinn Harbour\Põhi\18105_dp_haljastus_katuse.ifc" "C:\Users\simay\OneDrive\Desktop\sb_fme\new_data\Tallinn Harbour\Põhi\18105_dp_haljastus_muru.ifc" "C:\Users\simay\OneDrive\Desktop\sb_fme\new_data\Tallinn Harbour\Põhi\18105_dp_haljastus_puittaim.ifc" "C:\Users\simay\OneDrive\Desktop\sb_fme\new_data\Tallinn Harbour\Põhi\18105_dp_hoone.ifc" "C:\Users\simay\OneDrive\Desktop\sb_fme\new_data\Tallinn Harbour\Põhi\18105_dp_hoonestus.ifc" "C:\Users\simay\OneDrive\Desktop\sb_fme\new_data\Tallinn Harbour\Põhi\18105_dp_transp_klt_ratas.ifc" "C:\Users\simay\OneDrive\Desktop\sb_fme\new_data\Tallinn Harbour\Põhi\18105_dp_transp_tee.ifc" "C:\Users\simay\OneDrive\Desktop\sb_fme\new_data\Tallinn Harbour\Põhi\DP_Pohi_plan-ala+krunt.ifc""   # Source Industry Foundation Class (IFC) File(s)
- FEATURE_TYPES =   # " " Feature Types to Read
- CLIPTYPE = dp_plan_ala   # Clip on border or plot
- BORDERFILL = YES   # Workaround to fill boundary
- DATABASE_1 = New LADM Db   # Connection
- DATABASE_3 = New LADM Db   # Connection
- DATABASE_2 = New LADM Db   # Connection
- SourceDataset_CSV2 = $(FME_MF_DIR)output.csv   # Source CSV (Comma Separated Value) File(s)

Readers:
- IFC_1: IFC from $(SourceDataset_IFC) in EPSG:3301
- CSV2_2: CSV2 from $(SourceDataset_CSV2)

Writers:
- POSTGIS_4: POSTGIS to $(DATABASE_1)
- POSTGRES_3: POSTGRES to $(DATABASE_3)
- POSTGIS_6: POSTGIS to $(DATABASE_2)

Note: THIS WORKFLOW WORKS WITH THE "database_v13.sql" SCRIPT!!!
Creator
    GEOMTYPE = Geometry Object
    NUM = 1
    CREATED -> FeatureReader [INITIATOR]
FeatureReader
    ATTRIBUTES = IfcAnnotation,"GlobalId,Name,Description,ObjectType,3D,Body",IfcBuilding,"GlobalId,Name,Description,ObjectType,LongName,CompositionType,ElevationOfRefHeight,ElevationOfTerrain,BuildingAddress.Purpose,BuildingAddress.Description,BuildingAddress.UserDefinedPurpose,BuildingAddress.InternalLocation,BuildingAddress.AddressLines,BuildingAddress.PostalBox,BuildingAddress.Town,BuildingAddress.Region,BuildingAddress.PostalCode,BuildingAddress.Country,Body",IfcBuildingElementProxy,"GlobalId,Name,Description,ObjectType,Tag,PredefinedType,Body",IfcProject,"GlobalId,Name,Description,ObjectType,LongName,Phase,Body",IfcPropertySet,,IfcQuantitySet,,IfcRoad,"GlobalId,Name,Description,ObjectType,LongName,CompositionType,PredefinedType,3D,Body",IfcTypeObject,"ifc_type_name,ifc_unique_id,GlobalId,Name,Description,ApplicableOccurrence,Tag,ElementType,PredefinedType",PropertySetDefinition,,QuantitySetDefinition,
    ATTR_ACCUM_MODE = Only Use Result
    COMBINE_GEOM = Use Result
    COORDSYS = EPSG:3301
    DATASET = $(SourceDataset_IFC)
    FORMAT = IFC
    GEOMETRY_TYPES = IfcAnnotation,""",fme_area,fme_collection,fme_line,fme_point,fme_solid,fme_surface,fme_text""",IfcBuilding,""",fme_area,fme_collection,fme_line,fme_point,fme_solid,fme_surface,fme_text""",IfcBuildingElementProxy,""",fme_area,fme_collection,fme_line,fme_point,fme_solid,fme_surface,fme_text""",IfcProject,""",fme_area,fme_collection,fme_line,fme_point,fme_solid,fme_surface,fme_text""",IfcRoad,""",fme_area,fme_collection,fme_line,fme_point,fme_solid,fme_surface,fme_text"""
    IFC_ADD_PROJECTIONS = Yes
    IFC_CREATE_PQSET_DEFINITION_FEATURES = Yes
    IFC_EVALUATE_CSG_SOLIDS = No
    IFC_IFCSPACE_GEOMETRY = No
    IFC_MERGE_TYPE_OBJECT_PQSETS = YES
    IFC_PQSET_READ_MODE = FEATURES
    IFC_READER_MODE = Relational
    IFC_READER_VERSION = 2014
    IFC_READ_ALL_REPRESENTATIONS = YES
    IFC_SIMPLIFY_BASE_FACES = No
    IFC_SUBTRACT_OPENINGS = Yes
    IFC_TYPE_OBJECT_READ_MODE = MERGED
    IFC_USE_SEARCH_ENVELOPE = NO
    IFC_VERSION_OVERRIDE = auto-detect
    INTERACT = NONE
    ORDER_RESULTS = No
    OUTPUT_ADD_SCHEMA_ATTRIBUTES = NO
    OUTPUT_FEATURES_DISPLAY = Schema and Data Features
    IfcAnnotation -> AttributeExposer_5
    IfcBuildingElementProxy -> AttributeExposer_5
    IfcPropertySet -> AttributeExposer_12
    IfcTypeObject -> Tester_9
    IfcTypeObject -> Tester_23
Note: added 'dp_hoone' to @DISCIPLINES
dp_puittaim: Tester
    BOOL_OP = OR
    TEST_CLAUSE = TEST @Value(ifc_property_set_name) = dp_puittaim
    TEST_MODE = TEST
Note: LADM Part
Note: sysId / Planning identification number in database / planEesm / Main objective of the plan, similar to the establishment decision / planKSH / Strategic environmental assessment conducted during the process / planNim / Plan name as given in the establishment decision / PlanVide / Web link to the plan at the organizer's website / algaKp / Date of plan initiation
Junction_3
    -> GeometryRemover
Logger
    LOG_FEATURE = NONE
    MAXFEATS = 20
    MESSAGE = "FI: "
    SEVERITY = INFO
    LOGGED -> Terminator
Note: Some objects are excluded (trees) for dev purposes. There should be a rule on how to filter out / deal with trees
Terminator
    MESSAGE = Translation Terminated

Bookmark: Match Discipline
AttributeExposer_5
    ATTR_TABLE = ifc_property_set{0},
    -> Tester_7
Note: Element has propertyset
Tester_7
    BOOL_OP = OR
    TEST_CLAUSE = TEST ifc_property_set{0} ATTRIBUTE_HAS_A_VALUE ""
    TEST_MODE = TEST
    PASSED -> ListExploder_3
ListExploder_3
    ATTR_ACCUM_MODE = Merge List Attributes
    ATTR_CONFLICT_RES = Use List Attribute Values
    INDEX_ATTR = _element_index
    LIST_ATTR = ifc_property_set{}
    ELEMENTS -> FeatureMerger_3 [REQUESTOR]
AttributeExposer_12
    ATTR_TABLE = ifc_property_set_name,,ifc_unique_id,
    -> FeatureMerger_11 [REQUESTOR]
    -> dp_puittaim
FeatureMerger_11
    ATTR_ACCUM_MODE = Merge Supplier
    ATTR_CONFLICT_RES = Use Requestor
    IGNORE_NULLS = No
    JOIN_KEYS = @Value(ifc_property_set_name) @Value(predicted_discipline) AUTO
    MERGE_TYPE = Attributes Only
    PROCESS_DUPS = NO
    REJECT_NULL_MISSING_KEYS = No
    SUPPLIERS_FIRST = No
    MERGED -> FeatureMerger_3 [SUPPLIER]
Note: Element has propertyset according to disciplines
FeatureMerger_3
    ATTR_ACCUM_MODE = Merge Supplier
    ATTR_CONFLICT_RES = Use Requestor
    IGNORE_NULLS = No
    JOIN_KEYS = @Value(ifc_property_set) @Value(ifc_unique_id) AUTO
    MERGE_TYPE = Attributes Only
    PROCESS_DUPS = NO
    REJECT_NULL_MISSING_KEYS = No
    SUPPLIERS_FIRST = No
    MERGED -> AttributeManager_17
    MERGED -> FeatureMerger_5 [REQUESTOR]
    MERGED -> AttributeManager_18
    UNMERGED_REQUESTOR -> AttributeExposer

Bookmark: Exclude
Note: In Louna: tree is detailed type object
Tester_9
    BOOL_OP = OR
    TEST_CLAUSE:
      TEST @Value(Name) = Detailtree01
      TEST @Value(Name) = Concepttree01
    TEST_MODE = TEST
    PASSED -> FeatureMerger_4 [SUPPLIER]
Tester_3
    BOOL_OP = OR
    TEST_CLAUSE = TEST @Value(ifc_property_set_name) = dp_haljastus
    TEST_MODE = TEST
    PASSED -> AttributeExposer_6
    FAILED -> GeometryPartExtractor_2
AttributeExposer_6
    ATTR_TABLE = ifc_type_object_id,
    -> FeatureMerger_4 [REQUESTOR]
FeatureMerger_4
    ATTR_ACCUM_MODE = Merge Supplier
    ATTR_CONFLICT_RES = Use Requestor
    IGNORE_NULLS = No
    JOIN_KEYS = @Value(ifc_type_object_id) @Value(ifc_unique_id) AUTO
    MERGE_TYPE = Attributes Only
    PROCESS_DUPS = NO
    REJECT_NULL_MISSING_KEYS = No
    SUPPLIERS_FIRST = No
    UNMERGED_REQUESTOR -> GeometryPartExtractor_2

Bookmark: Get tree geometry
Tester_23
    BOOL_OP = OR
    TEST_CLAUSE = CASE_INSENSITIVE_TEST @Value(Name) CONTAINS tree
    TEST_MODE = CASE_INSENSITIVE_TEST
    PASSED -> AttributeExposer_11
AttributeExposer_11
    ATTR_TABLE = ifc_type,
    -> FeatureMerger_9 [SUPPLIER]
AttributeExposer
    ATTR_TABLE = massunit,,ifc_unique_id,,ifc_type_object_id,
    -> Tester
Tester
    BOOL_OP = OR
    TEST_CLAUSE = TEST massunit ATTRIBUTE_HAS_A_VALUE ""
    TEST_MODE = TEST
    PASSED -> FeatureMerger_9 [REQUESTOR]
FeatureMerger_9
    ATTR_ACCUM_MODE = Merge Supplier
    ATTR_CONFLICT_RES = Use Requestor
    IGNORE_NULLS = No
    JOIN_KEYS = @Value(ifc_type_object_id) @Value(ifc_unique_id) AUTO
    MERGE_TYPE = Attributes Only
    PROCESS_DUPS = NO
    REJECT_NULL_MISSING_KEYS = No
    SUPPLIERS_FIRST = No
    MERGED -> AttributeManager_6
AttributeManager_6
    ATTR_TABLE:
      REMOVE Name (buffer)
      REMOVE Description (buffer)
      REMOVE ObjectType (buffer)
      REMOVE 3D (buffer)
      REMOVE Body (buffer)
      REMOVE Tag (varchar(255))
      REMOVE PredefinedType (buffer)
      REMOVE ifc_property_set (varchar(200))
      REMOVE _element_index (uint32)
      REMOVE massunit (varchar(200))
    -> Aggregator_2
Aggregator_2
    ACCUM_ATTRS_NAME = Drop Incoming Attributes
    AGGREGATE_TYPE = Homogeneous Collection (If Possible)
    MODE = Geometry - Assemble One Level
    SEP = ,
    AGGREGATE -> GeometryExtractor
GeometryExtractor
    ATTR = geometry
    KIND_LONG = FME Binary
    REMOVE_GEOMETRY = No
    -> AttributeManager_7
AttributeManager_7
    ATTR_TABLE = SET_TO discipline (varchar(4)) = puud
    -> AttributeCreator_2

Bookmark: ML test discipline semantics
CSV (reader CSV2_2)
    attributes: ifc_unique_id varchar(28), predicted_discipline varchar(12)
    -> FeatureMerger_11 [SUPPLIER]

Bookmark: Check if plan_ala / dp_krunt is in disciplines
AttributeManager_17
    ATTR_TABLE = RENAME_SET_VALUE predicted_discipline > discipline (varchar(12))
    -> GeometryRemover_2
GeometryRemover_2
    REMOVE_COORDSYS = No
    -> Aggregator_4
Aggregator_4
    ACCUM_ATTRS_NAME = Drop Incoming Attributes
    AGGREGATE_TYPE = Homogeneous Collection (If Possible)
    GROUP_BY = discipline
    MODE = Geometry - Assemble One Level
    SEP = ,
    AGGREGATE -> Tester_10
Tester_10
    BOOL_OP = OR
    TEST_CLAUSE = TEST @Value(discipline) = $(CLIPTYPE)
    TEST_MODE = TEST
    PASSED -> NoFeaturesTester
NoFeaturesTester
    NoInput -> Logger
    -> FeatureMerger_5 [SUPPLIER]
FeatureMerger_5
    ATTR_ACCUM_MODE = Merge Supplier
    ATTR_CONFLICT_RES = Use Requestor
    IGNORE_NULLS = No
    JOIN_KEYS = 1 1 AUTO
    MERGE_TYPE = Attributes Only
    PROCESS_DUPS = NO
    REJECT_NULL_MISSING_KEYS = No
    SUPPLIERS_FIRST = No
    MERGED -> Tester_3

Bookmark: Geometryfilter en coercer
Note: Reading IFC in FME, body is often aggregated with property info. We want predictable geometry. We dont want aggregates. We only select body
GeometryPartExtractor_2
    GQUERY:
      for $geom in //geometry
      where $geom/@fme_geometry_name = 'Body'
      return number($geom/@fme_id)
    EXTRACTED -> Deaggregator_5
    EXTRACTED -> Tester_6
Note: Just to be sure
Deaggregator_5
    ATTR_ACCUM_MODE = Merge List Attributes
    ATTR_CONFLICT_RES = Use List Attribute Values
    EXPLODE_INSTANCES = No
    GEOM_NAME_FIELD = _geometry_name
    LIST_ATTR_MODE_LOOKUP = LEAN
    MODE = Flatten One Level
    PART_NUMBER_FIELD = _part_number
    SPLIT_COMPOSITES = No
    DEAGGREGATED -> Tester_14
    DEAGGREGATED -> GeometryExtractor_2
Tester_14
    BOOL_OP = OR
    TEST_CLAUSE:
      TEST @Value(discipline) = dp_krunt
      TEST @Value(discipline) = dp_plan_ala
    TEST_MODE = TEST
    PASSED -> Tester_15
    FAILED -> GeometryFilter_4

Bookmark: plan_ala
Note: get plan metadata from 'dp_plan_ala
Tester_6
    BOOL_OP = OR
    TEST_CLAUSE = TEST @Value(ifc_property_set_name) = dp_plan_ala
    TEST_MODE = TEST
    PASSED -> AttributeExposer_10
AttributeExposer_10
    ATTR_TABLE = planNim,,sysID,,algatKp,,planEesm,,planViide,,planKSH,,planID,
    -> NullAttributeMapper
Note: change empty values to null
NullAttributeMapper
    ATTRCHOICE = Selected Attributes
    ATTRLIST = _element_index 3D algatKp Body Description discipline GlobalId ifc_property_set ifc_property_set_name ifc_type_object_id ifc_unique_id Name ObjectType planEesm planNim planViide sysID
    NULL_TREATMENT = Null
    OTHER_VALUE = puudub
    SOURCE_ATTR_VAL = Null Empty "Missing (Selected Attributes Only)"
    -> Tester_2
Note: change seia assesment to boolean value
Tester_2
    BOOL_OP = OR
    TEST_CLAUSE = TEST @Value(planKSH) = Jah
    TEST_MODE = TEST
    PASSED -> true
    FAILED -> false
true: AttributeManager
    ATTR_TABLE = SET_TO planKSH (char(200)) = true
    -> Junction
Note: Jah: Yes / Ei: No
false: AttributeManager
    ATTR_TABLE = SET_TO planKSH (char(200)) = false
    -> Junction
Junction
    -> AttributeManager_3
AttributeManager_3
    ATTR_TABLE:
      REMOVE ObjectType (buffer)
      REMOVE _element_index (uint32)
      REMOVE ifc_property_set_name (varchar(200))
      RENAME_SET_VALUE planNim > name (varchar(200))
      RENAME_SET_VALUE algatKp > initiated_date (varchar(200))
      RENAME_SET_VALUE planEesm > planning_objective (varchar(200))
      RENAME_SET_VALUE planKSH > seia_conducted (char(200))
      REMOVE Name (buffer)
      REMOVE Description (buffer)
      REMOVE 3D (buffer)
      REMOVE Body (buffer)
      RENAME_SET_VALUE planID > plan_id (varchar(200))
      SET_TO la_source_id (uint16) = 999
    -> DateTimeStamper_2
    -> Junction_3
    -> GeometryRemover_5
    -> GeometryRemover_4
    -> AreaBuilder
GeometryRemover_4
    REMOVE_COORDSYS = No
    -> FeatureMerger_7 [REQUESTOR]

Bookmark: STEP 1: Store the source id in LA_Source
GeometryRemover
    REMOVE_COORDSYS = No
    -> Tester_5
Tester_5
    BOOL_OP = OR
    TEST_CLAUSE = TEST plan_id ATTRIBUTE_HAS_A_VALUE ""
    TEST_MODE = TEST
    PASSED -> DuplicateFilter_2
DuplicateFilter_2
    INPUT_ORDERED_CHOICE = No
    KEYATTR = plan_id
    UNIQUE -> la_source (writer POSTGRES_3)
la_source (writer POSTGRES_3)
    attributes: plan_id varchar(200)

Bookmark: EST_Detailed_Plan & EST_Detailed_Unit
Note: begin_life_version (date of uploading it to the database = NOW)
DateTimeStamper_2
    DATETIME_ATTR = begin_lifespan_version
    INCLUDE_FRAC_SECONDS = NO
    INCLUDE_OFFSET = NO
    STAMP_TYPE = datetime
    TIMEZONE = utc
    -> AttributeManager_5
Note: add latest version as default time, database will update automatically
Note: name / initiated_date / geometry (plan_ala) / seia_conducted / *begin_lifespan_version / source_id / organizer_reference / planning_objective
AttributeManager_5
    ATTR_TABLE:
      SET_TO begin_lifespan_lastversion (varchar(200)) = @Value(begin_lifespan_version)
      REMOVE la_source_id (uint16)
    -> FeatureMerger_2 [SUPPLIER]
Note: Because a unit of a plan cannot exist without the plan, EST_DetailedUnit is dependent on the newly created EST_DetailedPlan to match with the same plan. / To upload data to the est_detailed_unit class and ensure it links to the latest version of the same sysId plan uploaded previously to the est_detailed_plan, an SQL query is used to retrieve the detailed_plan_id of the latest version of a given planID.
Junction_2
    -> SQLExecutor_3 [INITIATOR]
    -> AttributeRemover_4
Note: cretae dummy value for no name if doesnt have a plan name
Tester_25
    BOOL_OP = OR
    TEST_CLAUSE = TEST name ATTRIBUTE_VALUE_NULL ""
    TEST_MODE = TEST
    PASSED -> AttributeManager_15
    FAILED -> est_detailed_plan (writer POSTGIS_4)

Bookmark: Step 2. EST_Detailed_Plan
GeometryRemover_5
    REMOVE_COORDSYS = No
    -> AttributeManager_4
FeatureMerger_7
    ATTR_ACCUM_MODE = Merge Supplier
    ATTR_CONFLICT_RES = Use Supplier
    IGNORE_NULLS = No
    JOIN_KEYS = 1 1 AUTO
    MERGE_TYPE = Attributes and Geometry
    PROCESS_DUPS = NO
    REJECT_NULL_MISSING_KEYS = No
    SUPPLIERS_FIRST = No
    MERGED -> AttributeManager_4
AttributeManager_4
    ATTR_TABLE:
      REMOVE ifc_property_set (varchar(200))
      REMOVE ifc_type_object_id (varchar(200))
      REMOVE la_source_id (uint16)
      RENAME_SET_VALUE planViide > organizer_reference (varchar(200))
      RENAME_SET_VALUE sysID > source_id (varchar(200))
      RENAME_SET_VALUE _geometry > geometry (buffer)
    -> Junction_2
    -> Tester_4
Tester_4
    BOOL_OP = OR
    TEST_CLAUSE = TEST geometry ATTRIBUTE_HAS_A_VALUE ""
    TEST_MODE = TEST
    PASSED -> FeatureMerger_2 [REQUESTOR]
FeatureMerger_2
    ATTR_ACCUM_MODE = Merge Supplier
    ATTR_CONFLICT_RES = Use Requestor
    IGNORE_NULLS = No
    JOIN_KEYS = 1 1 AUTO
    MERGE_TYPE = Attributes Only
    PROCESS_DUPS = NO
    REJECT_NULL_MISSING_KEYS = No
    SUPPLIERS_FIRST = No
    MERGED -> DuplicateFilter_4
DuplicateFilter_4
    INPUT_ORDERED_CHOICE = No
    KEYATTR = discipline ifc_unique_id
    UNIQUE -> AttributeManager_14
AttributeManager_14
    ATTR_TABLE:
      REMOVE Tag (varchar(255))
      REMOVE PredefinedType (buffer)
      REMOVE sysID (varchar(200))
      REMOVE ifc_property_set (varchar(200))
      REMOVE ifc_type_object_id (varchar(200))
      REMOVE planViide (varchar(200))
    -> Tester_25
AttributeManager_15
    ATTR_TABLE = SET_TO name (varchar(6)) = NONAME
    -> est_detailed_plan (writer POSTGIS_4)
est_detailed_plan (writer POSTGIS_4)
    attributes: name varchar(200), plan_id oid, initiated_date varchar(200), planning_objective varchar(200), organizer_reference varchar(200), seia_conducted char(200), begin_lifespan_version timestamp, geometry varchar, source_id varchar(200)

Bookmark: Extract Geometry
Note: Build a surface from the plan area
AreaBuilder
    ALLOW_CYCLES = No
    CHECK_CURVE_DIRECTION = No
    CONNECT_Z_MODE = First Wins
    CONSIDER_NODE_ELEVATION = no
    DEAGGREGATE_INPUT = Deaggregate
    DONUT_CREATION = Yes
    DROP_HOLES = No
    LINES_AS_SEGMENTS = No
    POLY_ACCUM_ATTRS_NAME = Use Attributes From One Feature
    SNAPTYPE_PARAM = None
    AREA -> Extruder
Note: Extrude surface a little for aesthetic reasons
Extruder
    DIRECTION = Specified
    EXTRUSION_X = 0.0
    EXTRUSION_Y = 0.0
    EXTRUSION_Z = 5
    EXTRUDED -> AppearanceSetter_2 [GEOMETRY]
    EXTRUDED -> AppearanceStyler_2
AppearanceStyler_2
    ALPHA = 1.0
    DIFFUSE_COLOR = 0.196078,0.843137,0.294118
    TEXTURE_CENTER_U = 0.0
    TEXTURE_CENTER_V = 0.0
    TEXTURE_ROTATION_ANGLE = 0.0
    TEXTURE_U_OFFSET = 0.0
    TEXTURE_U_SCALING_FACTOR = 1.0
    TEXTURE_U_SHEARING_FACTOR = 0.0
    TEXTURE_V_OFFSET = 0.0
    TEXTURE_V_SCALING_FACTOR = 1.0
    TEXTURE_V_SHEARING_FACTOR = 0.0
    TEXTURE_WRAP_DISPLAY = Repeat in U and V
    -> AppearanceSetter_2 [APPEARANCE]
Note: terrain=green
AppearanceSetter_2
    DEF_STORAGE = Create New Definitions
    GQUERY:
      for $geom in //geometry
      where $geom/count(parent::geometry) = 0
      return number($geom/@fme_id)
    SET_ON_SIDE = Front and Back Sides
    TEXTURE_MAPPING_TYPE_CHOICE = Surface Normal
    TEXTURE_U_OFFSET2 = 0.0
    TEXTURE_U_SCALE_FACTOR = 1.0
    TEXTURE_V_OFFSET2 = 0.0
    TEXTURE_V_SCALE_FACTOR = 1.0
    USE_EXISTING_TEXTURE_COORDINATES = No
    -> Aggregator
GeometryExtractor_2
    ATTR = geometry
    KIND_LONG = FME Binary
    REMOVE_GEOMETRY = No
    -> AttributeRemover_2
Note: removes all other attributes beside geometry
AttributeRemover_2
    REMOVE_ATTRS = ifc_property_set,ifc_property_set_name,_element_index,_geometry_name,_part_number,3D,Body,Description,ifc_type_object_id,Name,ObjectType,PredefinedType,Tag
    -> Deaggregator
Deaggregator
    ATTR_ACCUM_MODE = Merge List Attributes
    ATTR_CONFLICT_RES = Use List Attribute Values
    EXPLODE_INSTANCES = No
    GEOM_NAME_FIELD = _geometry_name
    LIST_ATTR_MODE_LOOKUP = LEAN
    MODE = Flatten One Level
    PART_NUMBER_FIELD = _part_number
    SPLIT_COMPOSITES = No
    DEAGGREGATED -> GeometryFilter_3
GeometryFilter_3
    FILTER_MODE = COMPLETE
    FILTER_MULTI = FILTER_TYPES]"MultiSurface Solid Surface GeometryInstance Aggregate Polygon Curve"]INSTANCES]INSTANTIATE]FME_CONTROLLER_QUERY_FILE]]FME_CONTROLLER_CHOICE]Complete
    Curve -> Tester_8
    Polygon -> GeometryValidator
    Surface -> AttributeExposer_2
    Surface -> GeometryValidator_2
    Solid -> AttributeExposer_2
    Solid -> GeometryValidator_2
Note: get only plan_ala from here
Tester_8
    BOOL_OP = OR
    TEST_CLAUSE = TEST @Value(discipline) = dp_plan_ala
    TEST_MODE = TEST
    PASSED -> AttributeExposer_2
AttributeExposer_2
    ATTR_TABLE = planID,
    -> AttributeKeeper
GeometryValidator_2
    ISSUE_ATTR_NAME = _issues
    PRESETS = Surfaces And Solids
    REPAIR = Yes
    RULES = SELF_INTERSECTING CHECK_HOLE_TOUCHING_POLYGON]No]CONNECT_Z_MODE_SI]FIRST_WINS]SELF_INTERSECTION_TOLERANCE]None]INTERSECT_ACROSS_MULTIS]No]FME_CONTROLLER_QUERY_FILE]transformers/dependencies/geometryvalidator8/SELF_INTERSECTING.fme]FME_CONTROLLER_CHOICE]SELF_INTERSECTING PLANAR_SURFACE CHECK_AREA]DO_NOT_CHECK_AREA]TOLERANCE_MODE]AUTO]TOLERANCE]<Unused>]ANGULAR_TOLERANCE_MODE]AUTO]ANGULAR_TOLERANCE]<Unused>]FME_CONTROLLER_QUERY_FILE]transformers/dependencies/geometryvalidator8/PLANAR_SURFACE.fme]FME_CONTROLLER_CHOICE]PLANAR_SURFACE SOLID_VOID_REPAIR FME_CONTROLLER_QUERY_FILE]transformers/dependencies/geometryvalidator8/SOLID_VOID_REPAIR.fme]FME_CONTROLLER_CHOICE]SOLID_VOID_REPAIR SHELL_VALIDATION FLIP_APPEARANCE_MODE]FLIP_APPEARANCES]FME_CONTROLLER_QUERY_FILE]transformers/dependencies/geometryvalidator8/SHELL_VALIDATION.fme]FME_CONTROLLER_CHOICE]SHELL_VALIDATION MISSING_TEXTURE_COORDINATES FME_CONTROLLER_QUERY_FILE]transformers/dependencies/geometryvalidator8/MISSING_TEXTURE_COORDINATES.fme]FME_CONTROLLER_CHOICE]MISSING_TEXTURE_COORDINATES SURFACE_ORIENTATION FME_CONTROLLER_QUERY_FILE]transformers/dependencies/geometryvalidator8/SURFACE_ORIENTATION.fme]FME_CONTROLLER_CHOICE]SURFACE_ORIENTATION SOLID_ORIENTATION FME_CONTROLLER_QUERY_FILE]transformers/dependencies/geometryvalidator8/SOLID_ORIENTATION.fme]FME_CONTROLLER_CHOICE]SOLID_ORIENTATION
    SUMMARY = Detailed
    PASSED -> SolidDissolver
Note: Mesh all geometrıes ınto one for detailed plan est_detailed_plan
SolidDissolver
    ACCUM_INPUT_ATTRS = NONE
    DEAGGREGATE_INPUT = Yes
    SOLID -> AppearanceSetter [HOLDER]
    SOLID -> AppearanceStyler
    SOLID -> AppearanceSetter [GEOMETRY]
AppearanceStyler
    ALPHA = 1.0
    DIFFUSE_COLOR = 1,0.270588,0.227451
    TEXTURE_CENTER_U = 0.0
    TEXTURE_CENTER_V = 0.0
    TEXTURE_ROTATION_ANGLE = 0.0
    TEXTURE_U_OFFSET = 0.0
    TEXTURE_U_SCALING_FACTOR = 1.0
    TEXTURE_U_SHEARING_FACTOR = 0.0
    TEXTURE_V_OFFSET = 0.0
    TEXTURE_V_SCALING_FACTOR = 1.0
    TEXTURE_V_SHEARING_FACTOR = 0.0
    TEXTURE_WRAP_DISPLAY = Repeat in U and V
    -> AppearanceSetter [APPEARANCE]
Note: buildings=red
AppearanceSetter
    DEF_STORAGE = Create New Definitions
    GQUERY:
      for $geom in //geometry
      where $geom/count(parent::geometry) = 0
      return number($geom/@fme_id)
    SET_ON_SIDE = Front and Back Sides
    TEXTURE_MAPPING_TYPE_CHOICE = Surface Normal
    TEXTURE_U_OFFSET2 = 0.0
    TEXTURE_U_SCALE_FACTOR = 1.0
    TEXTURE_V_OFFSET2 = 0.0
    TEXTURE_V_SCALE_FACTOR = 1.0
    USE_EXISTING_TEXTURE_COORDINATES = No
    -> Offsetter
Note: Offset the terrain extrusion so its above terrain again
Offsetter
    MODE = Cartesian Coordinate
    XOFF = 0
    YOFF = 0
    ZOFF = 5
    OFFSET -> Aggregator
Note: Terrain + Buildings
Aggregator
    ACCUM_ATTRS_NAME = Merge Incoming Attributes
    AGGREGATE_TYPE = Homogeneous Collection (If Possible)
    MODE = Geometry - Assemble One Level
    SEP = ,
    AGGREGATE -> Offsetter_2
Offsetter_2
    MODE = Cartesian Coordinate
    XOFF = 0
    YOFF = 0
    ZOFF = -5
    OFFSET -> GeometryExtractor_3
Note: merged geometry
GeometryExtractor_3
    ATTR = _geometry
    KIND_LONG = FME Binary
    REMOVE_GEOMETRY = No
    -> FeatureMerger_7 [SUPPLIER]

Bookmark: Geometry Validation
Note: There are issues iin the geometry
GeometryValidator
    ISSUE_ATTR_NAME = _issues
    PRESETS = Surfaces And Solids
    REPAIR = Yes
    RULES = SELF_INTERSECTING CHECK_HOLE_TOUCHING_POLYGON]No]CONNECT_Z_MODE_SI]FIRST_WINS]SELF_INTERSECTION_TOLERANCE]None]INTERSECT_ACROSS_MULTIS]No]FME_CONTROLLER_QUERY_FILE]transformers/dependencies/geometryvalidator8/SELF_INTERSECTING.fme]FME_CONTROLLER_CHOICE]SELF_INTERSECTING PLANAR_SURFACE CHECK_AREA]DO_NOT_CHECK_AREA]TOLERANCE_MODE]AUTO]TOLERANCE]<Unused>]ANGULAR_TOLERANCE_MODE]AUTO]ANGULAR_TOLERANCE]<Unused>]FME_CONTROLLER_QUERY_FILE]transformers/dependencies/geometryvalidator8/PLANAR_SURFACE.fme]FME_CONTROLLER_CHOICE]PLANAR_SURFACE SOLID_VOID_REPAIR FME_CONTROLLER_QUERY_FILE]transformers/dependencies/geometryvalidator8/SOLID_VOID_REPAIR.fme]FME_CONTROLLER_CHOICE]SOLID_VOID_REPAIR SHELL_VALIDATION FLIP_APPEARANCE_MODE]FLIP_APPEARANCES]FME_CONTROLLER_QUERY_FILE]transformers/dependencies/geometryvalidator8/SHELL_VALIDATION.fme]FME_CONTROLLER_CHOICE]SHELL_VALIDATION MISSING_TEXTURE_COORDINATES FME_CONTROLLER_QUERY_FILE]transformers/dependencies/geometryvalidator8/MISSING_TEXTURE_COORDINATES.fme]FME_CONTROLLER_CHOICE]MISSING_TEXTURE_COORDINATES SURFACE_ORIENTATION FME_CONTROLLER_QUERY_FILE]transformers/dependencies/geometryvalidator8/SURFACE_ORIENTATION.fme]FME_CONTROLLER_CHOICE]SURFACE_ORIENTATION SOLID_ORIENTATION FME_CONTROLLER_QUERY_FILE]transformers/dependencies/geometryvalidator8/SOLID_ORIENTATION.fme]FME_CONTROLLER_CHOICE]SOLID_ORIENTATION
    SUMMARY = Detailed
    FAILED -> ListExploder
ListExploder
    ATTR_ACCUM_MODE = Merge List Attributes
    ATTR_CONFLICT_RES = Use List Attribute Values
    INDEX_ATTR = _element_index
    LIST_ATTR = _issues{}

Bookmark: Step 3. EST_Detailed_Unit
Note: get unit geometries
AttributeKeeper
    CREATE_BULK_MODE_FEATURES = NO
    KEEP_ATTRS = discipline,geometry,ifc_unique_id,GlobalId
    -> AttributeCreator_2
AttributeRemover_4
    REMOVE_ATTRS = geometry,organizer_reference,planning_objective,seia_conducted,ifc_unique_id
    -> GeometryRemover_3
Note: remove plan_ala geometry
GeometryRemover_3
    REMOVE_COORDSYS = No
    -> FeatureMerger [REQUESTOR]
AttributeCreator_2
    ATTR_TABLE = SET_TO join_key (uint8) = 1
    -> FeatureJoiner [LEFT]
Creator_4
    GEOMTYPE = Geometry Object
    NUM = 1
    CREATED -> SQLExecutor_3 [INITIATOR]
Note: Retrieve the detailed_plan_id of the most recent version of the plan with the given source_id. / The query sorts by begin_lifespan_version (date) and detailed_plan_id in descending order, limiting the result to the most recent entry.
SQLExecutor_3
    COMBINE_ATTRS = Result Attributes Only
    COMBINE_GEOM = Initiator Geometry Only
    DATASET = New LADM Db
    FORMAT = POSTGRES
    OUTPUT_FEATURES = DATA_ONLY
    POSTGRES_CREATE_FEATURE_TABLES_FROM_DATA = Yes
    POSTGRES_NAMED_CONNECTION = New LADM Db
    POSTGRES_QUERY_FEATURE_TYPES_FOR_MERGE_FILTERS = Yes
    POSTGRES_READ_TIME_WITH_TIMEZONE = Yes
    SQL_STATEMENT:
      SELECT detailed_plan_id
      FROM est_detailed_plan
      WHERE plan_id = '@Value(plan_id)'
      ORDER BY begin_lifespan_version DESC, detailed_plan_id DESC
      LIMIT 1;
    RESULT -> AttributeExposer_3
AttributeExposer_3
    ATTR_TABLE = detailed_plan_id,
    -> DateTimeStamper
Note: begin_life_version (date of uploading it to the database = NOW)
DateTimeStamper
    DATETIME_ATTR = begin_lifespan_version
    INCLUDE_FRAC_SECONDS = NO
    INCLUDE_OFFSET = NO
    STAMP_TYPE = datetime
    TIMEZONE = utc
    -> FeatureMerger [SUPPLIER]
FeatureMerger
    ATTR_ACCUM_MODE = Merge Supplier
    ATTR_CONFLICT_RES = Use Requestor
    IGNORE_NULLS = No
    JOIN_KEYS = 1 1 AUTO
    MERGE_TYPE = Attributes Only
    PROCESS_DUPS = NO
    REJECT_NULL_MISSING_KEYS = No
    SUPPLIERS_FIRST = No
    MERGED -> DuplicateFilter
DuplicateFilter
    INPUT_ORDERED_CHOICE = No
    KEYATTR = GlobalId
    UNIQUE -> AttributeCreator
AttributeCreator
    ATTR_TABLE = SET_TO join_key (uint8) = 1
    -> FeatureJoiner [RIGHT]
FeatureJoiner
    ATTR_CONFLICT_RES = Prefer Left
    GEOMETRY_HANDLING = Prefer Left
    JOIN_KEYS = join_key join_key AUTO
    JOIN_MODE = Inner
    JOINED -> GeometryCoercer
Note: compute current_area and current_volume for each geometry unit
GeometryCoercer
    GQUERY:
      for $geom in //geometry
      where $geom/count(parent::geometry) = 0
      return number($geom/@fme_id)
    KIND = fme_polygon
    COERCED -> VolumeCalculator
    UNTOUCHED -> VolumeCalculator
VolumeCalculator
    MULT = 1
    SET_TRAIT = No
    VOLUME_ATTR = current_volume
    -> SurfaceFootprintReplacer
    -> FeatureMerger_8 [REQUESTOR]
Note: add 3D geometry again
FeatureMerger_8
    ATTR_ACCUM_MODE = Merge Supplier
    ATTR_CONFLICT_RES = Use Requestor
    IGNORE_NULLS = No
    JOIN_KEYS = @Value(ifc_unique_id) @Value(ifc_unique_id) AUTO
    MERGE_TYPE = Attributes Only
    PROCESS_DUPS = NO
    REJECT_NULL_MISSING_KEYS = No
    SUPPLIERS_FIRST = No
    MERGED -> FeatureMerger_6 [REQUESTOR]
Note: add additional attributes to write
FeatureMerger_6
    ATTR_ACCUM_MODE = Merge Supplier
    ATTR_CONFLICT_RES = Use Requestor
    IGNORE_NULLS = No
    JOIN_KEYS = @Value(ifc_unique_id) @Value(ifc_unique_id) AUTO
    MERGE_TYPE = Attributes Only
    PROCESS_DUPS = NO
    REJECT_NULL_MISSING_KEYS = No
    SUPPLIERS_FIRST = No
    MERGED -> AttributeManager_2
    UNMERGED_REQUESTOR -> Tester_11
Note: trees
Tester_11
    BOOL_OP = OR
    TEST_CLAUSE = TEST @Value(discipline) = puud
    TEST_MODE = TEST
    PASSED -> AttributeManager_2
Note: add latest version as default time, database will update automatically
AttributeManager_2
    ATTR_TABLE:
      RENAME_SET_VALUE GlobalId > global_id (char(22))
      SET_TO begin_lifespan_lastversion (varchar(200)) = @Value(begin_lifespan_version)
    -> Tester_19
Note: excl. plan_ala
Tester_19
    BOOL_OP = OR
    TEST_CLAUSE = TEST @Value(discipline) != dp_plan_ala
    TEST_MODE = TEST
    PASSED -> Tester_13
    FAILED -> Junction_4
Tester_24
    BOOL_OP = OR
    TEST_CLAUSE = TEST @Value(discipline) = dp_plan_ala
    TEST_MODE = TEST
    PASSED -> GeometryFilter_2
    FAILED -> DuplicateFilter_3
Note: remove plan_ala surface again
GeometryFilter_2
    FILTER_MODE = COMPLETE
    FILTER_MULTI = FILTER_TYPES]"Polygon Solid"]INSTANCES]INSTANCE]FME_CONTROLLER_QUERY_FILE]]FME_CONTROLLER_CHOICE]Complete
    Solid -> DuplicateFilter_3
DuplicateFilter_3
    INPUT_ORDERED_CHOICE = No
    KEYATTR = geometry discipline ifc_unique_id
    UNIQUE -> Tester_26
Note: cretae dummy value for no name if doesnt have a plan name
Tester_26
    BOOL_OP = OR
    TEST_CLAUSE = TEST name ATTRIBUTE_VALUE_NULL ""
    TEST_MODE = TEST
    PASSED -> AttributeManager_16
    FAILED -> est_detailed_unit (writer POSTGIS_6)
AttributeManager_16
    ATTR_TABLE = SET_TO name (varchar(6)) = NONAME
    -> est_detailed_unit (writer POSTGIS_6)
est_detailed_unit (writer POSTGIS_6)
    attributes: global_id char(22), geometry varchar, name varchar(200), source_id varchar(200), initiated_date int8, detailed_plan_id varchar(200), begin_lifespan_version timestamp, current_area float8, current_volume float8, max_height_indications varchar(200), begin_lifespan_lastversion varchar(200), discipline varchar, description varchar(200), floor_above_ground varchar(200), floor_below_ground varchar(200), depth_below_ground varchar(200), conditions varchar(200), element_type varchar(200), surface_relation int8

Bookmark: Plan_ala / dp_krunt
Note: clip area is either plan_ala or krunt
Tester_15
    BOOL_OP = OR
    TEST_CLAUSE = TEST @Value(discipline) = $(CLIPTYPE)
    TEST_MODE = TEST
    PASSED -> AttributeExposer_8
Note: Border should be ifcannotation
AttributeExposer_8
    ATTR_TABLE = fme_feature_type,
    -> Tester_16
Tester_16
    BOOL_OP = OR
    TEST_CLAUSE = TEST @Value(fme_feature_type) = IfcAnnotation
    TEST_MODE = TEST
    PASSED -> NoFeaturesTester_2
NoFeaturesTester_2
    -> AttributeExposer_9
AttributeExposer_9
    ATTR_TABLE = planID,,objectID,,nimetus,,tingimus,,pind,
    -> 2DForcer
Note: make 2d polygon
2DForcer
    2D -> LineCloser
LineCloser
    CONNECT_Z_MODE = First Wins
    AREA -> AttributeKeeper_2
AttributeKeeper_2
    CREATE_BULK_MODE_FEATURES = NO
    KEEP_ATTRS = GlobalId,ifc_property_set,ifc_property_set_name,ifc_unique_id,planID,nimetus,objectID,pind,tingimus
    -> Counter_2
Counter_2
    CNT_ATTR = nr
    DOMAIN = counter
    SCOPE = Global
    START = 1

Bookmark: Other disciplines
Note: At this point I only expect this, and only encountered solids + surfaces, so not sure how to deal with the rest yet
GeometryFilter_4
    FILTER_MODE = SIMPLE
    FILTER_MULTI = FILTER_TYPES]"Null Area Surface Solid"]FME_CONTROLLER_QUERY_FILE]]FME_CONTROLLER_CHOICE]Simple
    Surface -> GeometryCoercer_2
    Solid -> GeometryCoercer_2
GeometryCoercer_2
    GQUERY:
      for $geom in //geometry
      where $geom/count(parent::geometry) = 0
      return number($geom/@fme_id)
    KIND = fme_composite_surface
    COERCED -> Deaggregator_6
Deaggregator_6
    ATTR_ACCUM_MODE = Merge List Attributes
    ATTR_CONFLICT_RES = Use List Attribute Values
    EXPLODE_INSTANCES = No
    GEOM_NAME_FIELD = _geometry_name
    LIST_ATTR_MODE_LOOKUP = LEAN
    MODE = Flatten One Level
    PART_NUMBER_FIELD = _part_number
    SPLIT_COMPOSITES = Yes
    DEAGGREGATED -> 2DForcer_2
2DForcer_2
    2D -> GeometryFilter_5
GeometryFilter_5
    FILTER_MODE = SIMPLE
    FILTER_MULTI = FILTER_TYPES]Area]FME_CONTROLLER_QUERY_FILE]]FME_CONTROLLER_CHOICE]Simple

Bookmark: Add other metadata coming
AttributeManager_18
    ATTR_TABLE = RENAME_SET_VALUE predicted_discipline > discipline (varchar(12))
    -> AttributeExposer_7
AttributeExposer_7
    ATTR_TABLE = korgus,,nimetus,,korrus_mal,,korrus_mpe,,sygavus,,tingimus,,jaotuskiht,,max_abs_h,
    -> Tester_20
    -> Tester_21
    -> Tester_22
Junction_5
    -> NullAttributeMapper_2
NullAttributeMapper_2
    ATTRCHOICE = Selected Attributes
    ATTRLIST = _element_index conditions depth_below_ground description element_type floor_above_ground floor_below_ground ifc_property_set ifc_unique_id max_height_indications 3D Body Description discipline GlobalId ifc_property_set_name jaotuskiht korgus korrus_mal korrus_mpe max_abs_h Name nimetus ObjectType PredefinedType sygavus Tag tingimus
    NULL_TREATMENT = Missing
    SOURCE_ATTR_VAL = Null
    -> FeatureMerger_6 [SUPPLIER]

Bookmark: Max_height_indications
Note: korgus
Tester_20
    BOOL_OP = AND
    TEST_CLAUSE:
      TEST @Value(discipline) = dp_hoonestus
      TEST korgus ATTRIBUTE_HAS_A_VALUE ""
    TEST_MODE = TEST
    PASSED -> AttributeManager
AttributeManager
    ATTR_TABLE:
      REMOVE ifc_property_set_name (varchar(200))
      REMOVE discipline (buffer)
      RENAME_SET_VALUE korgus > max_height_indications (varchar(200))
      REMOVE GlobalId (char(22))
      REMOVE Name (buffer)
      REMOVE Description (buffer)
      REMOVE ObjectType (buffer)
      REMOVE 3D (buffer)
      REMOVE Body (buffer)
      REMOVE Tag (varchar(255))
      REMOVE PredefinedType (buffer)
      RENAME_SET_VALUE nimetus > description (varchar(200))
      RENAME_SET_VALUE korrus_mal > floor_below_ground (varchar(200))
      RENAME_SET_VALUE korrus_mpe > floor_above_ground (varchar(200))
      RENAME_SET_VALUE sygavus > depth_below_ground (varchar(200))
      RENAME_SET_VALUE tingimus > conditions (varchar(200))
      RENAME_SET_VALUE jaotuskiht > element_type (varchar(200))
      REMOVE max_abs_h (varchar(200))
    -> Junction_5
Note: max_abs_h
Tester_21
    BOOL_OP = COMPOSITE
    COMPOSITE_TEST = 1 AND 2
    TEST_CLAUSE:
      TEST @Value(discipline) = dp_hoone
      TEST max_abs_h ATTRIBUTE_HAS_A_VALUE ""
    TEST_MODE = TEST
    PASSED -> AttributeManager_13
AttributeManager_13
    ATTR_TABLE:
      REMOVE ifc_property_set_name (varchar(200))
      REMOVE discipline (buffer)
      REMOVE korgus (varchar(200))
      REMOVE GlobalId (char(22))
      REMOVE Name (buffer)
      REMOVE Description (buffer)
      REMOVE ObjectType (buffer)
      REMOVE 3D (buffer)
      REMOVE Body (buffer)
      REMOVE Tag (varchar(255))
      REMOVE PredefinedType (buffer)
      RENAME_SET_VALUE nimetus > description (varchar(200))
      RENAME_SET_VALUE korrus_mal > floor_below_ground (varchar(200))
      RENAME_SET_VALUE korrus_mpe > floor_above_ground (varchar(200))
      RENAME_SET_VALUE sygavus > depth_below_ground (varchar(200))
      RENAME_SET_VALUE tingimus > conditions (varchar(200))
      RENAME_SET_VALUE jaotuskiht > element_type (varchar(200))
      RENAME_SET_VALUE max_abs_h > max_height_indications (varchar(200))
    -> Junction_5
Note: neither have a value
Tester_22
    BOOL_OP = AND
    TEST_CLAUSE:
      TEST korgus ATTRIBUTE_IS_MISSING ""
      TEST max_abs_h ATTRIBUTE_IS_MISSING ""
    TEST_MODE = TEST
    PASSED -> Junction_5

Bookmark: Calculate Area (footprint)
SurfaceFootprintReplacer
    LIGHT_X = 0
    LIGHT_Y = 0
    LIGHT_Z = 1
    SHADOW_MODE = Perpendicular Shadow
    FOOTPRINT -> AreaCalculator
AreaCalculator
    AREA_ATTR = current_area
    AREA_TYPE = Plane Area
    MULT = 1
    -> GeometryRemover_6
Note: Remove now 2D geometry
GeometryRemover_6
    REMOVE_COORDSYS = No
    -> FeatureMerger_8 [SUPPLIER]

Bookmark: LA_Surface_Relation Codelist
Tester_13
    BOOL_OP = COMPOSITE
    COMPOSITE_TEST = 1 OR 2 OR ( 3 AND 4 )
    TEST_CLAUSE:
      TEST @Value(discipline) = dp_transp
      TEST @Value(discipline) = dp_plan_ala
      TEST @Value(discipline) = dp_haljastus
      TEST @Value(element_type) = muru
    TEST_MODE = TEST
    PASSED -> AttributeManager_9
    FAILED -> Tester_18
Note: On Ground
AttributeManager_9
    ATTR_TABLE = SET_TO surface_relation (uint8) = 4
    -> Junction_4
Tester_18
    BOOL_OP = AND
    TEST_CLAUSE:
      TEST @Value(floor_above_ground) > 0
      TEST @Value(floor_below_ground) > 0
    TEST_MODE = TEST
    PASSED -> AttributeManager_11
    FAILED -> Tester_12
Note: Mix
AttributeManager_11
    ATTR_TABLE = SET_TO surface_relation (uint8) = 1
    -> Junction_4
Tester_12
    BOOL_OP = OR
    TEST_CLAUSE:
      TEST @Value(element_type) = maapealne
      TEST @Value(floor_above_ground) > 0
      TEST @Value(discipline) = puud
    TEST_MODE = TEST
    PASSED -> AttributeManager_8
    FAILED -> Tester_17
Note: Above
AttributeManager_8
    ATTR_TABLE = SET_TO surface_relation (uint8) = 3
    -> Junction_4
Tester_17
    BOOL_OP = COMPOSITE
    COMPOSITE_TEST = 1 OR 2 AND 3
    TEST_CLAUSE:
      TEST depth_below_ground ATTRIBUTE_HAS_A_VALUE ""
      TEST @Value(floor_below_ground) > 0
      TEST @Value(floor_above_ground) = 0
    TEST_MODE = TEST
    PASSED -> AttributeManager_10
    FAILED -> AttributeManager_12
Note: Below
AttributeManager_10
    ATTR_TABLE = SET_TO surface_relation (uint8) = 2
    -> Junction_4
Note: NULL
AttributeManager_12
    ATTR_TABLE = SET_TO surface_relation (varchar(14)) = FME_NULL_VALUE
    -> Junction_4
Junction_4
    -> Tester_24

FME custom transformer NoFeaturesTester
Description
This transformer checks whether there are any input features. If not, then a single feature is ouput via the NoInput port. If Input features exist, then they are output via the Output port.
Other transformers often generate features that signify an error condition. This transformer can be used to check for those features and if those features exists, then a separate action can be triggered.
Example 
This may be useful to test if any data emerges from a reader, when the 'Ignore Failed Readers' advanced parameter is set to yes.
Input Ports 
Input: Features to be checked for existence. Any features will be accepted. 
Output Ports
NoInput:
If no input features exist, a single featue is returned via the NoInput port. 
Output: 
Any feature that entered the Input port is returned via the Output port.

Input (input)
    -> Sampler
    -> Output (output)
Output (output)
Sampler
    RATE = 1
    SAMPLE_MODE = No
    SAMPLE_TYPE_LONG = First N Features
    SAMPLED -> AttributeCreator_2
AttributeCreator_2
    ATTR_TABLE:
      SET_TO count (int8) = 0
      SET_TO remove (varchar(8)) = yes
    -> DuplicateFilter
Creator
    GEOMTYPE = Geometry Object
    NUM = 1
    CREATED -> AttributeCreator_3
AttributeCreator_3
    ATTR_TABLE = SET_TO no_features (varchar(8)) = true
    -> DuplicateFilter
DuplicateFilter
    INPUT_ORDERED_CHOICE = No
    KEYATTR = count
    UNIQUE -> Tester
Tester
    BOOL_OP = OR
    TEST_CLAUSE = TEST @Value(remove) != yes
    TEST_MODE = TEST
    PASSED -> AttributeRemover
AttributeRemover
    REMOVE_ATTRS = count,remove
    -> NoInput (output)
NoInput (output)
